submodule acme-types {
    yang-version "1.1";
    belongs-to acme-system {
        prefix "acme";
    }
    
    import ietf-yang-types {
        prefix "yang";
    }
    
    organization "ACME Inc.";
    contact
        "Joe L. User

         ACME, Inc.
         42 Anywhere Drive
         Nowhere, CA 95134
         USA

         Phone: +1 800 555 0100
         EMail: joe@acme.example.com";

    description
        "This submodule defines common ACME types.";
    
}
