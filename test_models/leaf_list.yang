module event {
    list foo {
        key bar;
        leaf bar {
            type string;
        }
        leaf-list baz1 {
            min-elements 2;
            type string;
        }
        leaf-list baz2 {
            max-elements 3;
            type string;
        }
        leaf-list baz3 {
            min-elements 2;
            max-elements 3;
            type string;
        }
        leaf-list baz4 {
            type string;
            max-elements 3;
            default "default1";
            default "default2";
            default "default3";
        }
    }
}
